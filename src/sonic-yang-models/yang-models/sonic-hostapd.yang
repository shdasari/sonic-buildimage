module sonic-hostapd {
    namespace "http://github.com/sonic-net/sonic-hostapd";
    prefix shostapd;
    yang-version 1.1;

    description
        "SONiC HOSTAPD";

    revision 2023-09-15 {
        description "Enhancement: Added LocalAuthentication Support, Contributed by CG.";
    }

    revision 2023-08-02 {
        description "Initial revision.";
    }

    typedef auth_type_enumeration {
        type enumeration {
            enum eap-md5;
            enum chap;
            enum pap;
        }
    }

    container sonic-hostapd {
        description "HOSTAPD top level container.";

        container HOSTAPD_GLOBAL_CONFIG {
            description
                "Container for hostapd global config.";

            list HOSTAPD_GLOBAL_CONFIG_LIST {
                key "global";

                leaf global {
                    type enumeration {
                        enum GLOBAL;
                    }
                    description
                        "Configure dot1x/hostapd global configuration.";
                }

                leaf dot1x_system_auth_control {
                    type boolean;
                    description
                        "Indicates whether dot1x/hostapd is enabled/disabled on the switch.";
                }
            }
        }

        container HOSTAPD_USER_CONFIG {
            description
                "Container for hostapd user config.";
                
            list USER_CONFIG_LIST {
                key "username";
                description "User configuration for HOSTAPD";
    
                leaf username {
                    type string {
                        length 1..32;
                    }
                    description "Username of the user";
                }
    
                leaf password {
                    type string {
                        length 1..255;
                    }
                    description "Password of the user";
                }
    
                leaf auth_type {
                    type auth_type_enumeration;
                    default "eap-md5";
                    description "Auth type for the user";
                }
    
                leaf vlan_id {
                    type uint16 {
                        range 1..4095;
                    }
                    description "VLAN ID associated with the authorized client";
                }
    
                leaf session_timeout {
                    type uint32;
                    description "Client session timeout in seconds";
                }
            }
        }
    }
}
